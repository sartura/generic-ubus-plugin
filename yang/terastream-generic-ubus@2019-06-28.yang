module terastream-generic-ubus {
     yang-version 1.1;
     namespace "https://terastream/ns/yang/terastream-generic-ubus";
     prefix "ts-gu";

     organization
        "Deutsche Telekom AG";

    contact
        "Landgrabenweg 151
        53227 Bonn, Germany";


     description
          "The module enables users to define necessary information for the
          generic ubus plugin. The informations for the generic ubus plugins
          are as follows:
               - mapping between ubus object and the YANG module for the
                 ubus object
               - methods (name and arguments) for an ubus object

          Additionaly RPC are defined for ubus objects that do not have a YANG
          module specified.
          ";

     revision "2019-06-28" {
          description "Add ubus object filtering support.";
     }
     revision "2019-06-12" {
          description "Add module install and feature enable RPC support.";
     }
     revision "2019-06-11" {
          description "Add multiple ubus object method calls in rpc.";
     }
     revision "2019-06-10" {
          description "Add rpc support for ubus calls.";
     }
     revision "2019-03-20" {
          description "Initial revision.";
     }


     container generic-ubus-config {
          description
               "Container for holding the necessary information for the
               generic ubus plugin.";

          leaf ubus-object-filter-file {
               description
                    "Path to file containing ubus object that are going to be
                    filtered out";
               type string;
          }

          list ubus-object {
               description
                    "List for every object for which the user wants to get the
                    state data. For every list ubus-object name and yang module
                    to use for the state data is mandatory. Method doesn't need
                    to be specified which means that NO method
                    will be executed.";
               key name;
               leaf name {
                    description "Ubus object name.";
                    mandatory true;
                    type string;
               }
                leaf yang-module {
                    description "Yang module name";
                    mandatory true;
                    type string;
               }
               list method {
                    description
                         "List of every method to be executon on a ubus object.
                         If a method is specified the method name is mandatory.
                         Method messagge is the method argument in JSON format.
                         The messagge doesn't have to be specified in that case
                         it will be treated as an empty JSON object ( '{}' ).";
                    key name;
                    leaf name {
                         description "Ubus object method name.";
                         mandatory true;
                         type string;
                    }
                    leaf message {
                         description
                              "Message to be passed to the ubus object method";
                         type string;
                    }
               }
          }
     }

     rpc ubus-call {
          description
               "RPC for implementig the ubus call for ubus object that do not
               have their YANG module implemented on the system.";
          status current;
          input {
               list ubus-invocation {
                    key "ubus-object ubus-method";
                    leaf ubus-object {
                         description "Ubus object name.";
                         mandatory true;
                         type string;
                    }
                    leaf ubus-method {
                         description "Ubus object method name.";
                         mandatory true;
                         type string;
                    }
                    leaf ubus-method-message {
                         description "Ubus object method message.";
                         type string;
                    }
               }
          }
          output {
               list ubus-result {
                    description "Ubus call result.";
                    key ubus-invocation;
                    leaf ubus-invocation {
                         description
                              "Ubus object, ubus method and message that was
                              invoked to produce this result";
                         type string;
                    }
                    leaf ubus-response {
                         description
                              "The response message of the invoked ubus call";
                         type string;
                    }
               }
          }
     }

     rpc module-install {
          description "RPC for installing a ubus specific YANG module.";
          status current;
          input {
               leaf-list module-name-full {
                    description
                    "Name of the module to be installed.
                    Path to module included";
                    type string;
               }
          }
          output {
               list module-install-result {
                    key module-name-full;
                    leaf module-name-full {
                         type string;
                    }
                    leaf module-install-status {
                         type string;
                    }
               }
          }
     }

     rpc feature-update {
          description
               "RPC for enabeling and disabeling features for a YANG module";
          status current;
          input {
               list feature-update-invocation {
                    key "module-name feature-name";
                    leaf module-name {
                         description
                              "Module for which a feature needs
                              to be enabled/disabled.";
                         mandatory true;
                         type string;
                    }
                    leaf feature-name {
                         description
                              "Feature that needs to be enabled/disabled.";
                         mandatory true;
                         type string;
                    }
                    choice feature-action {
                         description
                              "Desired operation. Either enable or disable a feature";
                         mandatory true;
                         case enable-action {
                              container enable {
                                   presence
                                        "Enable feature if this conatiner is present.";
                              }
                         }
                         case disable-action {
                              container disable {
                                   presence
                                        "Disabeling feature if this conatiner is present.";
                              }
                         }
                    }
               }
          }
          output {
               list feature-update-result {
                    key feature-invocation-full;
                    leaf feature-invocation-full {
                         type string;
                    }
                    leaf feature-update-status {
                         type string;
                    }
               }
          }
     }
}
